## Business Card App - Requirements Specification (RC-Hierarchy)

## Introduction (RC-Folder)
- PC-Description: <!--!-->This document describes the requirements for the business card management application. The card management application shall manage busienss contact/business card data.<!--!-->

## Requirements (RC-Folder)

## Functional requirements (RC-Folder)

## Business card management (RC-Requirement)
- PC-Description: As user I want to manage business card data to get an overview about my business contacts.<!--!-->
- PC-RequirementType: V-RequirementType-0

## CRUD (RC-Requirement)
- PC-Description: The app shall provide the user with the ability to create, update and delete business card data sets.<!--!-->
- PC-RequirementType: V-RequirementType-0

## Business card overview (RC-Requirement)
- PC-Description: The app shall display the available buisness crads in an overview-view to the user.
  Similar to this paper-mockup:
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- PC-RequirementType: V-RequirementType-0

## Display no card text (RC-Requirement)
- PC-Description: When no business card data is available (no cards), the app shall display the text "No cards available." instead of a card list.<!--!-->
- PC-RequirementType: V-RequirementType-0

## Selection of business cards (RC-Requirement)
- PC-Description: The app shall provide the user with the ability to select a single business card in preparation of an update or delete operation.<!--!-->
- PC-RequirementType: V-RequirementType-0

## Buttons for operations (RC-Requirement)
- PC-Description: The app shall provide the user buttons to start the create, update or delete operation.<!--!-->
- PC-RequirementType: V-RequirementType-0

## Card editor (RC-Requirement)
- PC-Description: When a create operation or an update operation is started, the app shall provide the user with the ability to edit the single data of a business card (business card editor).
- PC-RequirementType: V-RequirementType-0

## Card editor form (RC-Requirement)
- PC-Description: The card editor shall be realized like a typical web form.<!--!-->
- PC-RequirementType: V-RequirementType-0

## Edit behavior (RC-Requirement)
- PC-Description: When the card editor is visible, the app shall provide the user with the ability to confirm or cancel the edit operation for the currently selected card.
- PC-RequirementType: V-RequirementType-0

## Delete operation (RC-Requirement)
- PC-Description: When a card is selected the app shall provide the user with the ability to delete the selected card.<!--!-->
- PC-RequirementType: V-RequirementType-0

## Card data specification (RC-Requirement)
- PC-Description: The business card data objects shall consist of the following properties:
  - Title (e.g. 'Dr.')
  - First Name
  - Last Name
  - Company
  - Street
  - House Number
  - Zip code
  - City
  - Phone
  - Mobile phone
  - E-Mail
- PC-RequirementType: V-RequirementType-0

## Non-functional requirements (RC-Folder)

## Technology (RC-Requirement)
- PC-Description: <!--!-->The app shall be realized as a web-based application with a bowser-based UI.<!--!-->
- PC-RequirementType: V-RequirementType-2

## Data storage (RC-Requirement)
- PC-Description: The app shall store the card data in a JSON-format-based file in the App-Data directory of the current user.<!--!-->
- PC-RequirementType: V-RequirementType-2

## Implementation technology (RC-Requirement)
- PC-RequirementType: V-RequirementType-2
- PC-Description: The app shall be realized using the ASP.NET Blazor technology.<!--!-->
